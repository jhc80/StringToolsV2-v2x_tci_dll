Ieee1GMV2X {iso(1) identified-organization(3) ieee(111)
standards-association-numbered-series-standards(2) wave-stds(1609)  dot2(2)
scms(4) errors(2) complete (1) major-version-2(2)}

DEFINITIONS AUTOMATIC TAGS ::= BEGIN

EXPORTS ALL;

Uint3 ::= INTEGER (0..7)
Uint8 ::= INTEGER (0..255)
Uint16 ::= INTEGER (0..65535)
Uint32 ::= INTEGER (0..4294967295)
Uint64 ::= INTEGER (0..9223372036854775807)
CrlSeries ::= Uint16
Opaque ::= OCTET STRING
HashedId8 ::= OCTET STRING (SIZE(8))
HashedId3 ::= OCTET STRING (SIZE(3))
HashedId10 ::= OCTET STRING (SIZE(10))
Time32 ::= Uint32
Time64 ::= Uint64
HashAlgorithm ::= ENUMERATED{
	sgdsm3,
	sha256,
	sha3-256,
	...
}
CipherText ::= Opaque
SymmetricAlgorithm::= ENUMERATED {
	sgdsm4ecb ,
	sgdsm4cbc ,
	sgdsm4cfb ,
	sgdsm4ofb ,
	aes128ccm,
	...
}


EccCurve ::= ENUMERATED{
	sgdsm2,
	nistP256,
	brainpoolP256r1,
	...
}

CircularRegion ::=SEQUENCE {
	center TwoDLocation,
	radius Uint16
}

TwoDLocation ::=SEQUENCE {
	latitude Latitude,
	longitude Longitude
}


NinetyDegreeInt ::= INTEGER {
	min (-900000000),
	max (900000000),
	unknown (900000001)
	} (-900000000..900000001)

Latitude ::= NinetyDegreeInt
KnownLatitude ::= NinetyDegreeInt (min..max)
UnknownLatitude ::= NinetyDegreeInt (unknown)

Longitude ::= OneEightyDegreeInt
OneEightyDegreeInt ::= INTEGER {
	min (-1799999999),
	max (1800000000),
	unknown (1800000001)
} (-1799999999..1800000001)

KnownLongitude ::= OneEightyDegreeInt (min..max)
UnknownLongitude ::= OneEightyDegreeInt (unknown)

RectangularRegion ::=SEQUENCE {
	northWest TwoDLocation,
	southEast TwoDLocation
}
SequenceOfRectangularRegion ::= SEQUENCE OF RectangularRegion
GeographicRegion ::= CHOICE {
	circularRegion CircularRegion,
	rectangularRegion SequenceOfRectangularRegion,
	polygonalRegion PolygonalRegion,
	...
}



PolygonalRegion ::= SEQUENCE SIZE(3..MAX) OF TwoDLocation

ECCPoint::= CHOICE {
	x-only OCTET STRING (SIZE (32)),
	fill NULL, -- consistency w 1363 / X9.62
	compressed-y-0 OCTET STRING (SIZE (32)),
	compressed-y-1 OCTET STRING (SIZE (32)),
	uncompressed SEQUENCE {
		x OCTET STRING (SIZE (32)),
		y OCTET STRING (SIZE (32))
	}
}


PublicVerifyKey::= SEQUENCE{
	curve EccCurve,
	key ECCPoint
}

PublicEncryptionKey ::= SEQUENCE {
	supportedSymmAlg SymmetricAlgorithm,
	eccCurve EccCurve,
	publicKey ECCPoint
}

SubjectType::= ENUMERATED {
	enrollmentCredential,
	authorizationTicket,
	authorizationAuthority,
	enrollmentAuthority,
	rootCa,
	crlSigner
}

SubjectInfo ::= SEQUENCE {
	subjectType SubjectType,
	subjectName OCTET STRING (SIZE(0..32))
}


ItsAid ::= Uint64

ItsAidSsp::= SEQUENCE {
	itsAid ItsAid,
	serviceSpecificPermissions OCTET STRING(SIZE(1..32))
}

SubjectAssurance ::= OCTET STRING(SIZE(1))
SequenceOfitsAidList ::= SEQUENCE OF ItsAid
SequenceOfitsAidSspList ::= SEQUENCE OF ItsAidSsp
SubjectAttribute ::= SEQUENCE{
	verificationKey PublicVerifyKey,
	encryptionKey PublicEncryptionKey OPTIONAL,
	assuranceLevel SubjectAssurance OPTIONAL,
	itsAidList SequenceOfitsAidList OPTIONAL,
	itsAidSspList SequenceOfitsAidSspList OPTIONAL,
	...
}

TimeStartAndEnd ::= SEQUENCE {
	startValidity Time32,
	endValidity Time32
	}
ValidityPeriod ::= CHOICE{
	timeEnd Time32,
	timeStartAndEnd TimeStartAndEnd
	}
ValidityRestriction ::= SEQUENCE {
	validityPeriod ValidityPeriod,
	region GeographicRegion OPTIONAL,
	...
	}

TbsCert ::= SEQUENCE{
	subjectInfo SubjectInfo,
	subjectAttributes SubjectAttribute,
	validityRestrictions ValidityRestriction
}

CertificateDigest::= SEQUENCE {
	algorithm HashAlgorithm,
	digest HashedId8
}

IssuerId::= CHOICE {
	self NULL,
	certificateDigest CertificateDigest,
	...
	}


Signature ::= SEQUENCE {
	curve EccCurve,
	r ECCPoint,
	s OCTET STRING (SIZE (32))
	}

Certificate ::= SEQUENCE {
	version Uint8,
	issuerId IssuerId,
	tbs TbsCert,
	signature Signature
}	


RevokeInfo ::= SEQUENCE{
	id HashedId10,
	hashAlg HashAlgorithm,
	expiry Time32 OPTIONAL,
	...
}

SequenceOfRevokeInfo ::= SEQUENCE OF RevokeInfo

ToBeSignedCrl ::=SEQUENCE{
	crlSerial Uint32,
	issueDate Time32,
	nextCrl Time32,
	entries SequenceOfRevokeInfo
	}

Crl ::= SEQUENCE{
	version Uint8,
	issuerId IssuerId,
	unsignedCrl ToBeSignedCrl,
	signature Signature
	}
Elevation ::= Uint16
ThreeDLocation ::= SEQUENCE {
	latitude Latitude,
	longitude Longitude,
	elevation Elevation
	}

HeaderInfo ::= SEQUENCE{
	itsAid INTEGER,
	hashAlg HashAlgorithm OPTIONAL,
	genTime Time64 OPTIONAL,
	expiryTime Time64 OPTIONAL,
	location ThreeDLocation OPTIONAL,
	digest HashedId3 OPTIONAL,
	encKey PublicEncryptionKey OPTIONAL
	}


TBSData ::= SEQUENCE{
	headerInfo HeaderInfo,
	data OCTET STRING (SIZE(0..MAX)) OPTIONAL,
	extHash OCTET STRING (SIZE(32)) OPTIONAL
}

SequenceOfCertificate ::= SEQUENCE OF Certificate

SignerInfo ::= CHOICE {
	self NULL,
	certificate SequenceOfCertificate,
	certificateDigest CertificateDigest,
	...
}


SignedData ::= SEQUENCE{
	signer SignerInfo,
	tbs TBSData,
	sign Signature
}


SM4CipherTextCbc ::= SEQUENCE{
	iv OCTET STRING (SIZE(16)),
	cipher CipherText
	}

AesCcmCipherText ::= SEQUENCE{
	nonce OCTET STRING (SIZE(12)),
	cipher CipherText
	}



SymmetricCipherText ::= CHOICE{
	sm4Ecb CipherText,
	sm4Cbc SM4CipherTextCbc,
	sm4Cfb SM4CipherTextCbc,
	sm4Ofb SM4CipherTextCbc,
	aesCcm AesCcmCipherText
	}


EciesEncryptedKey::= SEQUENCE {
	eccCcurve EccCurve,
	v ECCPoint,
	c OCTET STRING(SIZE(16)),
	t OCTET STRING(SIZE(32))
	}

PKRecipientInfo ::= SEQUENCE{
	hashAlg HashAlgorithm,
	recipientId HashedId8,
	kek EciesEncryptedKey
}
PreSharedKeyRecipientInfo ::= SEQUENCE{
	hashAlg HashAlgorithm,
	symKeyHash HashedId8
	}
SymmRecipInfo ::= SEQUENCE {
	hashAlg HashAlgorithm,
	recipientId HashedId8,
	encKey SymmetricCipherText
}
RecipientInfo ::= CHOICE{
	pskRecipientInfo PreSharedKeyRecipientInfo,
	symmRecipInfo SymmRecipInfo,
	certRecipInfo PKRecipientInfo,
	signedDataRecipInfo PKRecipientInfo
	}


SequenceOfRecipientInfo ::=  SEQUENCE OF RecipientInfo

EncryptedData ::= SEQUENCE{
	recipients SequenceOfRecipientInfo,
	cipherText SymmetricCipherText
}



Payload ::= CHOICE{
	unSecuredData Opaque,
	signedData SignedData,
	encData EncryptedData
}

SecureMessage ::= SEQUENCE{
	version Uint8,
	payload Payload
}



CertRequest ::= SEQUENCE {
		version  Uint8,
		currentTime Time32,
		tbsCertData TbsCert,
		encryptionKey PublicEncryptionKey OPTIONAL
}





EnrollmentCertRequestData ::= SecureMessage(WITH COMPONENTS {...,
	version(2),
	payload(WITH COMPONENTS { ...,
		signedData(WITH COMPONENTS { ...,
			signer(WITH COMPONENTS { ...,
				certificate(SequenceOfCertificate(SIZE(1))),
				certificateDigest
			}),
			tbs(WITH COMPONENTS { ...,
				headerInfo(WITH COMPONENTS { ...,
					hashAlg PRESENT,
					genTime PRESENT
				}),
				extHash ABSENT
			}),
			sign(WITH COMPONENTS { ...,
				r(WITH COMPONENTS {...,
					x-only,compressed-y-0,compressed-y-1
				})
			})
		})
	})
})


EnrollmentCertRespData ::= SecureMessage(WITH COMPONENTS { ...,
	version(2),
	payload(WITH COMPONENTS { ...,
		encData(WITH COMPONENTS { ...,
			recipients(SequenceOfRecipientInfo (SIZE(1)) (CONSTRAINED BY {
				RecipientInfo(WITH COMPONENTS {
					signedDataRecipInfo
				})
			}))
		})
	})
})


EnrollmentCertResp ::= SecureMessage(WITH COMPONENTS { ...,
	version(2),
	payload(WITH COMPONENTS { ...,
		signedData(WITH COMPONENTS { ...,
			signer(WITH COMPONENTS {
				certificate(SequenceOfCertificate(SIZE(1)))
			}),
			tbs(WITH COMPONENTS { ...,
				headerInfo(WITH COMPONENTS { ...,
					itsAid(40962),
					hashAlg PRESENT,
					genTime PRESENT,
					expiryTime ABSENT,
					digest ABSENT,
					encKey ABSENT
				}),
				data(CONTAINING EnrollmentCertRespData),
				extHash  ABSENT
			})
		})
	})
})




NormalCertRequest ::= CertRequest(WITH COMPONENTS { ...,
	version(2),
	tbsCertData(WITH COMPONENTS { ...,
		subjectAttributes(WITH COMPONENTS { ...,
            assuranceLevel ABSENT,
            itsAidList ABSENT,
            itsAidSspList ABSENT
		}),
		validityRestrictions(WITH COMPONENTS { ...,
               region PRESENT
		})		
	}),
	encryptionKey PRESENT
})


NormalCertRequestEnc ::= SecureMessage(WITH COMPONENTS { ...,
	version(2),
	payload(WITH COMPONENTS { ...,
		encData(WITH COMPONENTS { ...,
			recipients(SequenceOfRecipientInfo (SIZE(1)) (CONSTRAINED BY {
				RecipientInfo(WITH COMPONENTS {
					certRecipInfo
				})
			}))
		})
	})
})


NormalCertRequestSign ::= SecureMessage(WITH COMPONENTS { ...,
	version(2),
	payload(WITH COMPONENTS { ...,
		signedData(WITH COMPONENTS { ...,
			signer(WITH COMPONENTS {
			certificate(SequenceOfCertificate(SIZE(1)))
			}),
			tbs(WITH COMPONENTS { ...,
				headerInfo(WITH COMPONENTS { ...,
					itsAid(40963),
					hashAlg PRESENT,
					genTime PRESENT,
					expiryTime ABSENT,
					digest ABSENT,
					encKey  ABSENT
				}),
				data( CONTAINING NormalCertRequestEnc ),
				extHash  ABSENT
			})
		})
	})
})


NormalCertRespData ::= SecureMessage(WITH COMPONENTS { ...,
	version(2),
	payload(WITH COMPONENTS { ...,
		encData(WITH COMPONENTS { ...,
			recipients(SequenceOfRecipientInfo (SIZE(1)) (CONSTRAINED BY {
				RecipientInfo(WITH COMPONENTS {
					signedDataRecipInfo
				})
			}))
		})
	})
})

NormalCertResp ::= SecureMessage(WITH COMPONENTS { ...,
	version(2),
	payload(WITH COMPONENTS { ...,
		signedData(WITH COMPONENTS { ...,
			signer(WITH COMPONENTS {
			certificate(SequenceOfCertificate(SIZE(1)))
			}),
			tbs(WITH COMPONENTS { ...,
				headerInfo(WITH COMPONENTS { ...,
					itsAid(40964),
					hashAlg PRESENT,
					genTime PRESENT,
					expiryTime ABSENT,
					digest ABSENT,
					encKey  ABSENT
				}),
				data( CONTAINING NormalCertRespData ),
				extHash  ABSENT
			})
		})
	})
})






SignedMessage ::= SecureMessage(WITH COMPONENTS {...,
	version(2),
	payload(WITH COMPONENTS { ...,
		signedData(WITH COMPONENTS { ...,
			signer(WITH COMPONENTS { ...,
				certificate(SequenceOfCertificate(SIZE(1))),
				certificateDigest
			}),
			tbs(WITH COMPONENTS { ...,
				headerInfo(WITH COMPONENTS { ...,
					hashAlg PRESENT,
					genTime PRESENT
				}),
				extHash ABSENT
			}),
			sign(WITH COMPONENTS { ...,
				r(WITH COMPONENTS {...,
					x-only,compressed-y-0,compressed-y-1
				})
			})
		})
	})
})


StaticEncryptMessage ::= SecureMessage(WITH COMPONENTS {...,
	version(2),
	payload(WITH COMPONENTS { ...,
		encData(WITH COMPONENTS { ...,
			recipients(SequenceOfRecipientInfo (SIZE(1)) (CONSTRAINED BY {
				RecipientInfo(WITH COMPONENTS {
					pskRecipientInfo
				})
			}))
		})
	})
})

EphemeralEncryptMessage ::= SecureMessage(WITH COMPONENTS {...,
	version(2),
	payload(WITH COMPONENTS { ...,
		encData(WITH COMPONENTS { ...,
			recipients(SequenceOfRecipientInfo (SIZE(1)) (CONSTRAINED BY {
				RecipientInfo(WITH COMPONENTS {
					certRecipInfo,signedDataRecipInfo
				})
			}))
		})
	})
})

SignEncryptMessage ::= SignedMessage(WITH COMPONENTS {...,
	version(2),
	payload(WITH COMPONENTS { ...,
		signedData(WITH COMPONENTS { ...,
			tbs(WITH COMPONENTS { ...,
				data( CONTAINING SecureMessage(WITH COMPONENTS {...,
					version(2),
					payload(WITH COMPONENTS { ...,
						encData
					})
				}))
			})
		})
	})
})



DHResult ::= ENUMERATED{
	success,
	refuse,
	stateError,
	timeOut,
	...
}

SequenceOfHashID8 ::= SEQUENCE OF HashedId8

ECDHData ::= SEQUENCE { 
	keyStartTime Time32,
	keyExpireTime Time32,
	dhKey ECCPoint,
	...
}

ECDHConfirm ::= SEQUENCE { 
	confirmDataS OCTET STRING (SIZE(32)),
	...
}

ECDHResult ::= SEQUENCE { 
	result DHResult,
	...
}


ECDHContent::=CHOICE { 
	exchangeData ECDHData,
	exchangeConfirm ECDHConfirm,
	exchangeResult ECDHResult,
	...
}

ECDHMessage::=SEQUENCE { 
	version Uint8,
	hashAlg HashAlgorithm,
	curve EccCurve,
	dhID  OCTET STRING (SIZE(16)),
	dhStartTime Time32 OPTIONAL,
	dhExpireTime Time32 OPTIONAL,
	dhData ECDHContent
}


ECDHExChangeData ::= ECDHMessage(WITH COMPONENTS { ...,
	version(2),
	dhStartTime  PRESENT,
	dhExpireTime PRESENT,
	dhData(WITH COMPONENTS { ...,
		exchangeData
	})
})


ECDHExChangeConfirmOrResult ::= ECDHMessage(WITH COMPONENTS { ...,
	version(2),
	dhStartTime  PRESENT,
	dhExpireTime PRESENT,
	dhData(WITH COMPONENTS { ...,
		exchangeConfirm,
		exchangeResult
	})
})

ECDHRequestData ::= SignedMessage(WITH COMPONENTS {...,
	payload(WITH COMPONENTS { ...,
		signedData(WITH COMPONENTS { ...,
			signer(WITH COMPONENTS { ...,
				certificate(SequenceOfCertificate(SIZE(1)))
			}),
			tbs(WITH COMPONENTS { ...,
				headerInfo(WITH COMPONENTS { ...,
					itsAid(41472),
					encKey  PRESENT
				}),
				data(CONTAINING SecureMessage(WITH COMPONENTS { ...,
					version(2),
					payload(WITH COMPONENTS { ...,
						unSecuredData(CONTAINING ECDHExChangeData)
					})
				}))
			})
		})
	})
})

ECDHResponseData ::= SignedMessage(WITH COMPONENTS {...,
	payload(WITH COMPONENTS { ...,
		signedData(WITH COMPONENTS { ...,
			signer(WITH COMPONENTS { ...,
				certificate(SequenceOfCertificate(SIZE(1)))
			}),
			tbs(WITH COMPONENTS { ...,
				headerInfo(WITH COMPONENTS { ...,
					itsAid(41472),
					encKey  PRESENT
				}),
				data(CONTAINING SecureMessage(WITH COMPONENTS { ...,
					version(2),
					payload(WITH COMPONENTS { ...,
						encData
					})
				}))
			})
		})
	})
})

ECDHConfirmOrResultData ::= SignedMessage(WITH COMPONENTS {...,
	payload(WITH COMPONENTS { ...,
		signedData(WITH COMPONENTS { ...,
			signer(WITH COMPONENTS { ...,
				certificate(SequenceOfCertificate(SIZE(1)))
			}),
			tbs(WITH COMPONENTS { ...,
				headerInfo(WITH COMPONENTS { ...,
					itsAid(41472),
					encKey  ABSENT
				}),
				data(CONTAINING SecureMessage(WITH COMPONENTS { ...,
					version(2),
					payload(WITH COMPONENTS { ...,
						encData
					})
				}))
			})
		})
	})
})




END
